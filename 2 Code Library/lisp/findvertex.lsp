;ignore, incomplete and replaced by deldupvertex
(defun C:FINDCLOSEVERTEX ()
	(setq vertex_index 0)
	(setq badlist nil)
	(if (null badlist)
		(search)
		(next)
	)
)

(defun search ()
	(foreach e (LM:ss->ent (ssget "X" (list (cons 0 "LWPOLYLINE"))))
		(setq prev nil)
		(setq done nil)
		(foreach p (LM:ent-pts e)
			(if (and (not (null prev)) (not done))
				(if (<= (dist prev p) 0)
					(progn (setq badlist (append badlist e)) (setq done T))
				)
			)
			(setq prev p)
		)
	)
)

(defun next ()
	;Zoom to (nth badlist vertex_index)
	(sssetfirst nil (ssadd (nth badlist vertex_index)))
)
