;Will auto run when AutoCAD starts, as long as it's in a support file path. Uncomment to load ArcGIS for AutoCAD, which should load automatically without this code.

; (defun S::startup()
; 	(command "netload" "C:\\Program Files\\ArcGIS for AutoCAD 370\\ArcGISForAutoCAD.dll")
; )
